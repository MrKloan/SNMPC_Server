Teracom DEFINITIONS ::= BEGIN

IMPORTS
   enterprises, IpAddress			FROM RFC1155-SMI
   DisplayString                	FROM RFC1213-MIB
   OBJECT-TYPE                  	FROM RFC-1212
   TRAP-TYPE                    	FROM RFC-1215;

teracom                           OBJECT IDENTIFIER ::=  { enterprises 38783 }

product                           OBJECT IDENTIFIER ::=  { teracom 1 }
snmpSetup                         OBJECT IDENTIFIER ::=  { teracom 2 }
monitorNcontrol                   OBJECT IDENTIFIER ::=  { teracom 3 }
network                           OBJECT IDENTIFIER ::=  { teracom 4 }
ioSetup                           OBJECT IDENTIFIER ::=  { teracom 5 }

ON-OFF          	::=   INTEGER { off(0), on(1) }
DACTION          	::=   INTEGER { noAction(0), mailIfOpenToClosed(1), mailIfClosedToOpen(2) }

name    OBJECT-TYPE
   SYNTAX DisplayString
   ACCESS read-only
   STATUS mandatory
   DESCRIPTION
      "Name of product. e.g. teracom.net etc."
   ::= { product 1 }
   

version    OBJECT-TYPE
   SYNTAX DisplayString
   ACCESS read-only
   STATUS mandatory
   DESCRIPTION
      "Version string. e.g. 1.0"
   ::= { product 2 }
   
date    OBJECT-TYPE
   SYNTAX DisplayString
   ACCESS read-only
   STATUS mandatory
   DESCRIPTION
      "Date of version"
   ::= { product 3 }


trapEnabled OBJECT-TYPE
    SYNTAX INTEGER { no(0), yes(1) }
    ACCESS read-write
    STATUS mandatory
    DESCRIPTION
        "Indicates if this trap entry is enabled or not."
    ::= { snmpSetup 1 }


trapReceiverIPAddress OBJECT-TYPE
    SYNTAX  IpAddress
    ACCESS  read-write
    STATUS mandatory
    DESCRIPTION
        "Trap receiver IP address"
    ::= { snmpSetup 2 }

trapCommunity OBJECT-TYPE
    SYNTAX  DisplayString (SIZE (0..13))
    ACCESS  read-write
    STATUS mandatory
    DESCRIPTION
        "Trap community to be used by agent to send trap"
    ::= { snmpSetup 3 }

digitalInput OBJECT-TYPE
    SYNTAX INTEGER { closed(0), open(1) }
    ACCESS  read-only
    STATUS mandatory
    DESCRIPTION
        "digital Input State"
    ::= { monitorNcontrol 1 }

relay1 OBJECT-TYPE
    SYNTAX ON-OFF
    ACCESS  read-write
    STATUS mandatory
    DESCRIPTION
        "relay1 State"
    ::= { monitorNcontrol 2 }

relay2 OBJECT-TYPE
    SYNTAX ON-OFF
    ACCESS  read-write
    STATUS mandatory
    DESCRIPTION
        "relay2 State"
    ::= { monitorNcontrol 3 }

relay3 OBJECT-TYPE
    SYNTAX ON-OFF
    ACCESS  read-write
    STATUS mandatory
    DESCRIPTION
        "relay3 State"
    ::= { monitorNcontrol 4 }

relay4 OBJECT-TYPE
    SYNTAX ON-OFF
    ACCESS  read-write
    STATUS mandatory
    DESCRIPTION
        "relay4 State"
    ::= { monitorNcontrol 5 }

relay5 OBJECT-TYPE
    SYNTAX ON-OFF
    ACCESS  read-write
    STATUS mandatory
    DESCRIPTION
        "relay5 State"
    ::= { monitorNcontrol 6 }

relay6 OBJECT-TYPE
    SYNTAX ON-OFF
    ACCESS  read-write
    STATUS mandatory
    DESCRIPTION
        "relay6 State"
    ::= { monitorNcontrol 7 }

relay7 OBJECT-TYPE
    SYNTAX ON-OFF
    ACCESS  read-write
    STATUS mandatory
    DESCRIPTION
        "relay7 State"
    ::= { monitorNcontrol 8 }

relay8 OBJECT-TYPE
    SYNTAX ON-OFF
    ACCESS  read-write
    STATUS mandatory
    DESCRIPTION
        "relay8 State"
    ::= { monitorNcontrol 9 }

pulse1 OBJECT-TYPE
    SYNTAX ON-OFF
    ACCESS  read-write
    STATUS mandatory
    DESCRIPTION
        "pulse1 State"
    ::= { monitorNcontrol 10 }

pulse2 OBJECT-TYPE
    SYNTAX ON-OFF
    ACCESS  read-write
    STATUS mandatory
    DESCRIPTION
        "pulse2 State"
    ::= { monitorNcontrol 11 }

pulse3 OBJECT-TYPE
    SYNTAX ON-OFF
    ACCESS  read-write
    STATUS mandatory
    DESCRIPTION
        "pulse3 State"
    ::= { monitorNcontrol 12 }

pulse4 OBJECT-TYPE
    SYNTAX ON-OFF
    ACCESS  read-write
    STATUS mandatory
    DESCRIPTION
        "pulse4 State"
    ::= { monitorNcontrol 13 }

pulse5 OBJECT-TYPE
    SYNTAX ON-OFF
    ACCESS  read-write
    STATUS mandatory
    DESCRIPTION
        "pulse5 State"
    ::= { monitorNcontrol 14 }

pulse6 OBJECT-TYPE
    SYNTAX ON-OFF
    ACCESS  read-write
    STATUS mandatory
    DESCRIPTION
        "pulse6 State"
    ::= { monitorNcontrol 15 }

pulse7 OBJECT-TYPE
    SYNTAX ON-OFF
    ACCESS  read-write
    STATUS mandatory
    DESCRIPTION
        "pulse7 State"
    ::= { monitorNcontrol 16 }

pulse8 OBJECT-TYPE
    SYNTAX ON-OFF
    ACCESS  read-write
    STATUS mandatory
    DESCRIPTION
        "pulse8 State"
    ::= { monitorNcontrol 17 }
	
allOn OBJECT-TYPE
    SYNTAX ON-OFF
    ACCESS  read-write
    STATUS mandatory
    DESCRIPTION
        "Set all relays ON"
    ::= { monitorNcontrol 18 }
	
allOff OBJECT-TYPE
    SYNTAX ON-OFF
    ACCESS  read-write
    STATUS mandatory
    DESCRIPTION
        "Set all relays OFF"
    ::= { monitorNcontrol 19 }
	
allPulse OBJECT-TYPE
    SYNTAX ON-OFF
    ACCESS  read-write
    STATUS mandatory
    DESCRIPTION
        "Pulse all relays"
    ::= { monitorNcontrol 20 }
	

deviceIPAddress OBJECT-TYPE
    SYNTAX  IpAddress
    ACCESS  read-write
    STATUS mandatory
    DESCRIPTION
        "Device IP address"
    ::= { network 1 }


subnetMask OBJECT-TYPE
    SYNTAX  IpAddress
    ACCESS  read-write
    STATUS mandatory
    DESCRIPTION
        "Subnet Mask"
    ::= { network 2 }

gateway OBJECT-TYPE
    SYNTAX  IpAddress
    ACCESS  read-write
    STATUS mandatory
    DESCRIPTION
        "Gateway IP address"
    ::= { network 3 }

deviceMACAddress OBJECT-TYPE
    SYNTAX  MacAddress
    ACCESS  read-write
    STATUS mandatory
    DESCRIPTION
        "Device MAC address"
    ::= { network 4 }

dhcpConfig OBJECT-TYPE
    SYNTAX INTEGER { off(0), on(1) }
    ACCESS read-write
    STATUS mandatory
    DESCRIPTION 
        "DHCP configuration ON/OFF"
    ::= { network 5 }

-- inputs	

--digitalInput1                               OBJECT IDENTIFIER ::=  { inputs 1 }
--digitalInput2                               OBJECT IDENTIFIER ::=  { inputs 2 }

relay1PulseDuration OBJECT-TYPE
    SYNTAX INTEGER (0..253)
    ACCESS read-write
    STATUS mandatory
    DESCRIPTION 
        "Pulse duration of relay1"
    ::= { ioSetup 1 }

relay2PulseDuration OBJECT-TYPE
    SYNTAX INTEGER (0..253)
    ACCESS read-write
    STATUS mandatory
    DESCRIPTION 
        "Pulse duration of relay2"
    ::= { ioSetup 2 }

relay3PulseDuration OBJECT-TYPE
    SYNTAX INTEGER (0..253)
    ACCESS read-write
    STATUS mandatory
    DESCRIPTION 
        "Pulse duration of relay3"
    ::= { ioSetup 3 }

relay4PulseDuration OBJECT-TYPE
    SYNTAX INTEGER (0..253)
    ACCESS read-write
    STATUS mandatory
    DESCRIPTION 
        "Pulse duration of relay4"
    ::= { ioSetup 4 }

relay5PulseDuration OBJECT-TYPE
    SYNTAX INTEGER (0..253)
    ACCESS read-write
    STATUS mandatory
    DESCRIPTION 
        "Pulse duration of relay5"
    ::= { ioSetup 5 }

relay6PulseDuration OBJECT-TYPE
    SYNTAX INTEGER (0..253)
    ACCESS read-write
    STATUS mandatory
    DESCRIPTION 
        "Pulse duration of relay6"
    ::= { ioSetup 6 }

relay7PulseDuration OBJECT-TYPE
    SYNTAX INTEGER (0..253)
    ACCESS read-write
    STATUS mandatory
    DESCRIPTION 
        "Pulse duration of relay7"
    ::= { ioSetup 7 }

relay8PulseDuration OBJECT-TYPE
    SYNTAX INTEGER (0..253)
    ACCESS read-write
    STATUS mandatory
    DESCRIPTION 
        "Pulse duration of relay8"
    ::= { ioSetup 8 }

relay1description  OBJECT-TYPE
    SYNTAX  DisplayString (SIZE (0..11))
    ACCESS read-write
    STATUS mandatory
    DESCRIPTION
        "Relay 1 description"
    ::= { ioSetup 9 }

relay2description  OBJECT-TYPE
    SYNTAX  DisplayString (SIZE (0..11))
    ACCESS read-write
    STATUS mandatory
    DESCRIPTION
        "Relay 2 description"
    ::= { ioSetup 10 }

relay3description  OBJECT-TYPE
    SYNTAX  DisplayString (SIZE (0..11))
    ACCESS read-write
    STATUS mandatory
    DESCRIPTION
        "Relay 3 description"
    ::= { ioSetup 11 }

relay4description  OBJECT-TYPE
    SYNTAX  DisplayString (SIZE (0..11))
    ACCESS read-write
    STATUS mandatory
    DESCRIPTION
        "Relay 4 description"
    ::= { ioSetup 12 }

relay5description  OBJECT-TYPE
    SYNTAX  DisplayString (SIZE (0..11))
    ACCESS read-write
    STATUS mandatory
    DESCRIPTION
        "Relay 5 description"
    ::= { ioSetup 13 }

relay6description  OBJECT-TYPE
    SYNTAX  DisplayString (SIZE (0..11))
    ACCESS read-write
    STATUS mandatory
    DESCRIPTION
        "Relay 6 description"
    ::= { ioSetup 14 }

relay7description  OBJECT-TYPE
    SYNTAX  DisplayString (SIZE (0..11))
    ACCESS read-write
    STATUS mandatory
    DESCRIPTION
        "Relay 7 description"
    ::= { ioSetup 15 }

relay8description  OBJECT-TYPE
    SYNTAX  DisplayString (SIZE (0..11))
    ACCESS read-write
    STATUS mandatory
    DESCRIPTION
        "Relay 8 description"
    ::= { ioSetup 16 }
	
digitalInputAction OBJECT-TYPE
	SYNTAX DACTION
	ACCESS read-write
	STATUS mandatory
	DESCRIPTION
		"Digital Input Action"
	::= { ioSetup 17 }
	
digitalInputTo  OBJECT-TYPE
    SYNTAX  DisplayString (SIZE (0..38))
    ACCESS read-write
    STATUS mandatory
    DESCRIPTION
        "Digital Input event receiver's e-mail address"
    ::= { ioSetup 18 }
	
digitalInputSubject  OBJECT-TYPE
    SYNTAX  DisplayString (SIZE (0..11))
    ACCESS read-write
    STATUS mandatory
    DESCRIPTION
        "Digital Input event e-mail's subject"
    ::= { ioSetup 19 }
	
digitalInputBody  OBJECT-TYPE
    SYNTAX  DisplayString (SIZE (0..22))
    ACCESS read-write
    STATUS mandatory
    DESCRIPTION
        "Digital Input event e-mail's body"
    ::= { ioSetup 20 }
	
relay1PulseDurationMs OBJECT-TYPE
    SYNTAX INTEGER (0..9)
    ACCESS read-write
    STATUS mandatory
    DESCRIPTION 
        "Pulse duration x 100 in miliseconds of relay1"
    ::= { ioSetup 21 }
	
relay2PulseDurationMs OBJECT-TYPE
    SYNTAX INTEGER (0..9)
    ACCESS read-write
    STATUS mandatory
    DESCRIPTION 
        "Pulse duration x 100 in miliseconds of relay2"
    ::= { ioSetup 22 }
	
relay3PulseDurationMs OBJECT-TYPE
    SYNTAX INTEGER (0..9)
    ACCESS read-write
    STATUS mandatory
    DESCRIPTION 
        "Pulse duration x 100 in miliseconds of relay3"
    ::= { ioSetup 23 }
	
relay4PulseDurationMs OBJECT-TYPE
    SYNTAX INTEGER (0..9)
    ACCESS read-write
    STATUS mandatory
    DESCRIPTION 
        "Pulse duration x 100 in miliseconds of relay4"
    ::= { ioSetup 24 }
	
relay5PulseDurationMs OBJECT-TYPE
    SYNTAX INTEGER (0..9)
    ACCESS read-write
    STATUS mandatory
    DESCRIPTION 
        "Pulse duration x 100 in miliseconds of relay5"
    ::= { ioSetup 25 }
	
relay6PulseDurationMs OBJECT-TYPE
    SYNTAX INTEGER (0..9)
    ACCESS read-write
    STATUS mandatory
    DESCRIPTION 
        "Pulse duration x 100 in miliseconds of relay6"
    ::= { ioSetup 26 }
	
relay7PulseDurationMs OBJECT-TYPE
    SYNTAX INTEGER (0..9)
    ACCESS read-write
    STATUS mandatory
    DESCRIPTION 
        "Pulse duration x 100 in miliseconds of relay7"
    ::= { ioSetup 27 }
	
relay8PulseDurationMs OBJECT-TYPE
    SYNTAX INTEGER (0..9)
    ACCESS read-write
    STATUS mandatory
    DESCRIPTION 
        "Pulse duration x 100 in miliseconds of relay8"
    ::= { ioSetup 28 }
	
digitalInputDescription  OBJECT-TYPE
    SYNTAX  DisplayString (SIZE (0..11))
    ACCESS read-write
    STATUS mandatory
    DESCRIPTION
        "Digital input description"
    ::= { ioSetup 29 }
	
configurationSaved OBJECT-TYPE
	SYNTAX INTEGER { unsaved(0), saved(1) }
	ACCESS read-write
	STATUS mandatory
	DESCRIPTION
		"Configuration save status SAVED/UNSAVED"
	::= { teracom 6 }

restartDevice OBJECT-TYPE
	SYNTAX INTEGER { cancel(0), restart(1) }
	ACCESS read-write
	STATUS mandatory
	DESCRIPTION
		"Restart Device"
	::= { teracom 7 }

trcDigitalInputState TRAP-TYPE
        ENTERPRISE teracom
        VARIABLES  {digitalInput}
        DESCRIPTION
            "This trap is sent each time when Digital Input changes its state"
       ::=  101
	   
trcRestartDevice TRAP-TYPE
        ENTERPRISE teracom
        VARIABLES  {restartDevice}
        DESCRIPTION
            "Device restart"
       ::=  102
END
